-- RRLP requires the imported partial modules from MAP(29.002): 
-- MAP-ExtensionDataTypes, MAP-LCS-DataTypes, 
--
-- MAP-ExtensionDataTypes module
MAP-ExtensionDataTypes {
   itu-t identified-organization (4) etsi (0) mobileDomain (0)
   gsm-Network (1) modules (3) map-ExtensionDataTypes (21) version13 (13)}

DEFINITIONS

IMPLICIT TAGS

::=

BEGIN

EXPORTS
        ExtensionContainer;


-- IOC for private MAP extensions


MAP-EXTENSION  ::= CLASS {
        &ExtensionType                          OPTIONAL,
        &extensionId    OBJECT IDENTIFIER }
        -- The length of the Object Identifier shall not exceed 16 octets and the
        -- number of components of the Object Identifier shall not exceed 16

-- data types

ExtensionContainer ::= SEQUENCE {
        privateExtensionList    [0]PrivateExtensionList OPTIONAL,
        pcs-Extensions  [1]PCS-Extensions       OPTIONAL,
        ...}

PrivateExtensionList ::= SEQUENCE SIZE (1..maxNumOfPrivateExtensions) OF
                                PrivateExtension

PrivateExtension ::= SEQUENCE {
        extId           MAP-EXTENSION.&extensionId
                                ({ExtensionSet}),
        extType         MAP-EXTENSION.&ExtensionType
                                ({ExtensionSet}{@extId})        OPTIONAL}

maxNumOfPrivateExtensions  INTEGER ::= 10

ExtensionSet            MAP-EXTENSION ::=
                {...
                 -- ExtensionSet is the set of all defined private extensions
        }
        -- Unsupported private extensions shall be discarded if received.

PCS-Extensions ::= SEQUENCE {
        ...}

END

-- MAP-LCS-DataTypes module

MAP-LCS-DataTypes {
   itu-t identified-organization (4) etsi (0) mobileDomain (0)
   gsm-Network (1) modules (3) map-LCS-DataTypes (25) version13 (13)}

DEFINITIONS
IMPLICIT TAGS
::=
BEGIN

EXPORTS
VelocityEstimate,
Ext-GeographicalInformation;

IMPORTS
;

Ext-GeographicalInformation ::= OCTET STRING (SIZE (1..maxExt-GeographicalInformation))
        -- Refers to geographical Information defined in 3GPP TS 23.032.
        -- This is composed of 1 or more octets with an internal structure according to
        -- 3GPP TS 23.032
        -- Octet 1: Type of shape, only the following shapes in 3GPP TS 23.032 are allowed:
        --              (a) Ellipsoid point with uncertainty circle
        --              (b) Ellipsoid point with uncertainty ellipse
        --              (c) Ellipsoid point with altitude and uncertainty ellipsoid
        --              (d) Ellipsoid Arc
        --              (e) Ellipsoid Point
        -- Any other value in octet 1 shall be treated as invalid
        -- Octets 2 to 8 for case (a) . Ellipsoid point with uncertainty circle
        --              Degrees of Latitude                             3 octets
        --              Degrees of Longitude                            3 octets
        --              Uncertainty code                                1 octet
        -- Octets 2 to 11 for case (b) . Ellipsoid point with uncertainty ellipse:
        --              Degrees of Latitude                             3 octets
        --              Degrees of Longitude                            3 octets
        --              Uncertainty semi-major axis                             1 octet
        --              Uncertainty semi-minor axis                             1 octet
        --              Angle of major axis                             1 octet
        --              Confidence                              1 octet
        -- Octets 2 to 14 for case (c) . Ellipsoid point with altitude and uncertainty ellipsoid
        --              Degrees of Latitude                             3 octets
        --              Degrees of Longitude                            3 octets
        --              Altitude                                2 octets
        --              Uncertainty semi-major axis                             1 octet
        --              Uncertainty semi-minor axis                             1 octet
        --              Angle of major axis                             1 octet
        --              Uncertainty altitude                            1 octet
        --              Confidence                              1 octet
        -- Octets 2 to 13 for case (d) . Ellipsoid Arc
        --              Degrees of Latitude                             3 octets
        --              Degrees of Longitude                            3 octets
        --              Inner radius                            2 octets
        --              Uncertainty radius                              1 octet
        --              Offset angle                            1 octet
        --              Included angle                          1 octet
        --              Confidence                              1 octet
        -- Octets 2 to 7 for case (e) . Ellipsoid Point
        --              Degrees of Latitude                             3 octets
        --              Degrees of Longitude                            3 octets

        --
        -- An Ext-GeographicalInformation parameter comprising more than one octet and
        -- containing any other shape or an incorrect number of octets or coding according
        -- to 3GPP TS 23.032 shall be treated as invalid data by a receiver.
        --
        -- An Ext-GeographicalInformation parameter comprising one octet shall be discarded
        -- by the receiver if an Add-GeographicalInformation parameter is received
        -- in the same message.
        --
        -- An Ext-GeographicalInformation parameter comprising one octet shall be treated as
        -- invalid data by the receiver if an Add-GeographicalInformation parameter is not
        -- received in the same message.

maxExt-GeographicalInformation  INTEGER ::= 20
        -- the maximum length allows for further shapes in 3GPP TS 23.032 to be included in later
        -- versions of 3GPP TS 29.002

VelocityEstimate ::= OCTET STRING (SIZE (4..7))
        -- Refers to Velocity description defined in 3GPP TS 23.032.
        -- This is composed of 4 or more octets with an internal structure according to
        -- 3GPP TS 23.032
        -- Octet 1: Type of velocity, only the following types in 3GPP TS 23.032 are allowed:
        --              (a) Horizontal Velocity
        --              (b) Horizontal with Vertical Velocity
        --              (c) Horizontal Velocity with Uncertainty
        --              (d) Horizontal with Vertical Velocity and Uncertainty
        -- For types Horizontal with Vertical Velocity and Horizontal with Vertical Velocity
        -- and Uncertainty, the direction of the Vertical Speed is also included in Octet 1
        -- Any other value in octet 1 shall be treated as invalid
        -- Octets 2 to 4 for case (a) Horizontal velocity:
        --              Bearing                         1 octet
        --              Horizontal Speed                2 octets
        -- Octets 2 to 5 for case (b) . Horizontal with Vertical Velocity:
        --              Bearing                         1 octet
        --              Horizontal Speed                2 octets
        --              Vertical Speed                  1 octet
        -- Octets 2 to 5 for case (c) . Horizontal velocity with Uncertainty:
        --              Bearing                         1 octet
        --              Horizontal Speed                2 octets
        --              Uncertainty Speed               1 octet
        -- Octets 2 to 7 for case (d) . Horizontal with Vertical Velocity and Uncertainty:
        --              Bearing                         1 octet
        --              Horizontal Speed                2 octets
        --              Vertical Speed                  1 octet
        --              Horizontal Uncertainty Speed    1 octet
        --              Vertical Uncertainty Speed      1 octet

END
